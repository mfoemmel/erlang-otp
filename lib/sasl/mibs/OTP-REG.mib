OTP-REG DEFINITIONS ::= BEGIN

IMPORTS
    MODULE-IDENTITY, enterprises
        FROM SNMPv2-SMI
    ;

otpRegModule MODULE-IDENTITY
    LAST-UPDATED "9712010900Z"
    ORGANIZATION "Ericsson, EPK/TE"
    CONTACT-INFO
       "Contact:  Erlang Support

         Postal:  ERICSSON SOFTWARE TECHNOLOGY AB
                  ERLANG SYSTEMS
                  Box 1214
                  S-164 28  KISTA, SWEDEN

             Tel: +46  8 719 00 00
          E-mail: support@erlang.ericsson.se"
    DESCRIPTION
       "The root MIB module for OTP."

    REVISION    "9902020900Z"
    DESCRIPTION
       "Cleaned up OBJECT IDENTIFIER registration.  Changed the name
       of the MODULE-IDENTITY of this module to non-conflicting name
       otpRegModule."

    REVISION    "9712010900Z"
    DESCRIPTION
       "The initial revision of MIB module OTP-REG."
    ::= { otpModules 1 }

ericsson       OBJECT IDENTIFIER ::= {enterprises 193}
otp            OBJECT IDENTIFIER ::= {ericsson 19}

-- sub-tree for registraions, including Modules
otpReg	       OBJECT IDENTIFIER ::= {otp 1}
otpModules     OBJECT IDENTIFIER ::= {otpReg 1}
-- otpTcModule         2
-- otpModule           3
-- otpOsMonModule      4
-- otpSnmpeaModule     5
-- otpEvaModule        6
-- otpLogModule        7
-- otpEvaLogModule     8
-- otpSnmpeaLogModule  9
-- otpMeshModule      10


-- sub-tree for OTP-wide objects and events
otpGeneric     OBJECT IDENTIFIER ::= {otp 2}

-- sub-tree for product specific objects and events
otpApplications
               OBJECT IDENTIFIER ::= {otp 3}
-- otpMib           1
-- otpOsMonMib      2
-- otpSnmpeaMib     3
-- otpEvaMib        4
-- otpLogMib        5
-- otpMeshMib       6


-- sub-tree for agent implementation capabilites
otpCaps	       OBJECT IDENTIFIER ::= {otp 4}
-- otpMibImplV10        1 (vsn of mib implementation, e.g. otp_mib)
-- otpOsMonMibImplV10   2
-- otpSnmpeaMibImplV10  3
-- otpEvaMibImplV10     4
-- otpLogMibImplV10     5


-- sub-tree for requirement specifications
otpReqs	       OBJECT IDENTIFIER ::= {otp 5}

-- sub-tree for experimental modules within OTP
otpExpr        OBJECT IDENTIFIER ::= {otp 6}

END
