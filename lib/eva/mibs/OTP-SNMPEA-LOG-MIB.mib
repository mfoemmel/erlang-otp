OTP-SNMPEA-LOG-MIB DEFINITIONS ::= BEGIN

IMPORTS
    MODULE-IDENTITY, OBJECT-IDENTITY, OBJECT-TYPE,
    IpAddress
        FROM SNMPv2-SMI
    MODULE-COMPLIANCE, OBJECT-GROUP
        FROM SNMPv2-CONF
    otpModules
        FROM OTP-REG
    otpSnmpeaMIBObjects, otpSnmpeaMIBCompliances, otpSnmpeaMIBGroups
        FROM OTP-SNMPEA-MIB
    logTransferIndex
        FROM OTP-LOG-MIB
    ;

otpSnmpeaLogModule MODULE-IDENTITY
    LAST-UPDATED  "0305090900Z"
    ORGANIZATION  "Ericsson"
    CONTACT-INFO
        "Contact:  Erlang Support see license agreement for Erlang/OTP."
    
    DESCRIPTION
        "This MIB is part of the OTP MIB.  It defines MIB objects
        for the Audit Trail logging mechanism in the extensible snmp
	agent.

        It uses the generic log mechanisms from OTP-LOG-MIB to control
        the log and the transfer of logs.  The logType of the log snmp
        audit trail log is 'snmpeaLogType'."

    
    REVISION	"0305090900Z"	
    DESCRIPTION		
        "Changed CONTACT-INFO as it was outdated, made it more generic
	to avoid such changes in the future. Also corrected a minor bug."
    
    REVISION    "9712010900Z"
    DESCRIPTION
        "The initial version of this MIB module."
    ::= { otpModules 9 }

snmpeaLog    OBJECT IDENTIFIER ::= { otpSnmpeaMIBObjects 2}     

-- The Snmpea Log group
--
-- The Snmpea Log group controls the snmp audit trail
-- log in the system.

snmpeaLogType OBJECT-IDENTITY
    STATUS     current
    DESCRIPTION
        "This identity is used as the logType for the snmp audit
        trail log in the system."
    ::= { snmpeaLog 1 }

snmpeaLogDiscriminator OBJECT-TYPE
    SYNTAX      INTEGER {
        none(1),
        readWrite(2),
        write(3)
        }
    MAX-ACCESS  read-write
    STATUS current
    DESCRIPTION
        "This attribute controls which requests are logged in the
        security audit trail log in the system."
    ::= { snmpeaLog 2 }

snmpeaLogTransferTable OBJECT-TYPE
    SYNTAX      SEQUENCE OF SnmpeaLogTransferEntry
    MAX-ACCESS  not-accessible
    STATUS      current
    DESCRIPTION
        "This table extends the logTransferTable."
    ::= { snmpeaLog 3 }

snmpeaLogTransferEntry OBJECT-TYPE
    SYNTAX      SnmpeaLogTransferEntry
    MAX-ACCESS  not-accessible
    STATUS      current
    DESCRIPTION
        ""
    INDEX      { logTransferIndex }
    ::= { snmpeaLogTransferTable 1 }

SnmpeaLogTransferEntry ::= SEQUENCE {
    snmpeaLogTransferIpAddress  IpAddress
    }

snmpeaLogTransferIpAddress OBJECT-TYPE
    SYNTAX      IpAddress
    MAX-ACCESS  read-write
    STATUS      current
    DESCRIPTION
        "If this attribute is set, log records from or to this
        ip address only are collected."
    ::= { snmpeaLogTransferEntry 1 }


-- conformance information

-- compliance statements

otpSnmpeaLogCompliance MODULE-COMPLIANCE
    STATUS  current
    DESCRIPTION
        "The compliance statement for OTP stystems that
        implement the OTP-SNMPEA-LOG-MIB."
    MODULE  -- this module
        MANDATORY-GROUPS { snmpeaLogGroup }

        GROUP snmpeaLogTransferGroup
        DESCRIPTION
            "This group is mandatory for agent systems that supports
            log transfer with FTP."
        OBJECT snmpeaLogDiscriminator
        MIN-ACCESS read-only
        DESCRIPTION
            "Read-write access is not required."  
    ::= { otpSnmpeaMIBCompliances 2 }


-- units of conformance

snmpeaLogGroup OBJECT-GROUP
    OBJECTS { snmpeaLogDiscriminator }
    STATUS  current
    DESCRIPTION
        "A collection of objects providing control of the audit
        trail log in the extensible snmp agent in the system."
    ::= { otpSnmpeaMIBGroups 5 }

snmpeaLogTransferGroup OBJECT-GROUP
    OBJECTS { snmpeaLogTransferIpAddress }              
    STATUS  current
    DESCRIPTION
        "A collection of objects providing control of the transfer
        of the snmp audit trail og in the system."
    ::= { otpSnmpeaMIBGroups 6 }


END
